ERLYVIDEO-MIB DEFINITIONS ::= BEGIN

IMPORTS
        MODULE-IDENTITY, OBJECT-TYPE, Gauge32, enterprises FROM SNMPv2-SMI

        OBJECT-GROUP FROM SNMPv2-CONF

        DisplayString FROM SNMPv2-TC;
        
        erlyvideo    MODULE-IDENTITY
                LAST-UPDATED "201008100000Z"
                ORGANIZATION "erlyvideo"
                CONTACT-INFO
                        "e-mail:	 info@erlyvideo.org"
                DESCRIPTION
                        "Erlyvideo SNMP"
                REVISION		 "201008100000Z"
                DESCRIPTION
                        "v1.0"
                ::= { enterprises 36342 }

demoGroups OBJECT IDENTIFIER ::= { erlyvideo 1 }
staticInfo OBJECT IDENTIFIER ::= { erlyvideo 2 }
dynamicOid OBJECT IDENTIFIER ::= { erlyvideo 3 }

--
-- Static OID members
--
nodeName
    OBJECT-TYPE
        SYNTAX DisplayString
        MAX-ACCESS read-only
        STATUS current
        DESCRIPTION "Node name"
        ::= { staticInfo 1 }

gaugeValue
    OBJECT-TYPE
        SYNTAX Gauge32
        MAX-ACCESS read-only
        STATUS current
        DESCRIPTION "Gauge value"
        ::= { staticInfo 2 }


--
-- Dynamic OID members
--
diskStatsTable OBJECT-TYPE
        SYNTAX SEQUENCE OF DiskStatsEntry
        MAX-ACCESS not-accessible
        STATUS current
        DESCRIPTION "Disk stats table"
        ::= { dynamicOid 1 }

diskStatsTableEntry OBJECT-TYPE
        SYNTAX DiskStatsEntry
        MAX-ACCESS not-accessible
        STATUS current
        DESCRIPTION "Disk stats entry"
        INDEX { mountPoint }
        ::= { diskStatsTable 1 }

DiskStatsEntry ::= SEQUENCE {
        mountPoint DisplayString,
        usePercent Gauge32
}

mountPoint OBJECT-TYPE
        SYNTAX DisplayString
        MAX-ACCESS read-only
        STATUS current
        DESCRIPTION "Disk mount point"
        ::= { diskStatsTableEntry 1 }

usePercent OBJECT-TYPE
        SYNTAX Gauge32
        MAX-ACCESS read-only
        STATUS current
        DESCRIPTION "Disk usage in percent"
        ::= { diskStatsTableEntry 2 }





virtualHostsTable OBJECT-TYPE
        SYNTAX SEQUENCE OF VirtualHostEntry
        MAX-ACCESS not-accessible
        STATUS current
        DESCRIPTION "virtual hosts table"
        ::= { dynamicOid 2 }

virtualHostsTableEntry OBJECT-TYPE
        SYNTAX VirtualHostEntry
        MAX-ACCESS not-accessible
        STATUS current
        DESCRIPTION "virtual hosts entry"
        INDEX { vhostName }
        ::= { virtualHostsTable 1 }

VirtualHostEntry ::= SEQUENCE {
        vhostName DisplayString,
        vhostAliases DisplayString
}

vhostName OBJECT-TYPE
        SYNTAX DisplayString
        MAX-ACCESS read-only
        STATUS current
        DESCRIPTION "virtual host name"
        ::= { virtualHostsTableEntry 1 }

vhostAliases OBJECT-TYPE
        SYNTAX DisplayString
        MAX-ACCESS read-only
        STATUS current
        DESCRIPTION "Disk usage in percent"
        ::= { virtualHostsTableEntry 2 }

--
-- Global Group
--
demoGroup OBJECT-GROUP
        OBJECTS {
                nodeName, gaugeValue, mountPoint, usePercent, vhostName, vhostAliases
        }
        STATUS current
        DESCRIPTION "Demo group"
        ::= { demoGroups 1 }

END
