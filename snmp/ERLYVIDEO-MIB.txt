-- erlyvideo SMI { enterprises 36342 }

ERLYVIDEO-MIB DEFINITIONS ::= BEGIN

IMPORTS
        MODULE-IDENTITY,
        OBJECT-IDENTITY,
	IpAddress,
	Counter64,
        enterprises
                FROM SNMPv2-SMI
        DisplayString,
                 FROM SNMPv2-TC
        MODULE-COMPLIANCE
                FROM SNMPv2-CONF;

erlyVideo MODULE-IDENTITY
        LAST-UPDATED "201010251000Z"
        ORGANIZATION "NoName Project."
        CONTACT-INFO
		"max@maxidors.org is contact person for this file.
                 max@maxidors.org is the final authority."
        DESCRIPTION
	    	"The Structure of Management Information for the
                erlyvideo Project enterprise MIB subtree."
	REVISION 	"200610311000Z"
        DESCRIPTION
                "Initial version of this MIB module."
        ::= { enterprises 36342 }        -- assigned by IANA

erlyVideoInfo OBJECT IDENTIFIER ::= { erlyVideo 1 }

erlyVideoInfoVersion OBJECT-TYPE
    	SYNTAX	DisplayString (SIZE(1..16))
	MAX-ACCESS	read-only
	STATUS		current
	DESCRIPTION
	    "Versiob of erlyVideo"
	::= { erlyVideoInfo 1 }

erlyVideoInfoMIBVersion OBJECT-TYPE
    	SYNTAX	INTEGER (1..255)
	MAX-ACCESS	read-only
	STATUS		current
	DESCRIPTION
	    "MAX Version of supported MIB"
	::= { erlyVideoInfo 2 }

erlyVideoInfoMemUsage	OBJECT-TYPE
    	SYNTAX		INTEGER (0..18446744073709551615)
	MAX-ACCESS	read-only
	STATUS		current
	DESCRIPTION
	    "Текущая занятая память"
	::= { erlyVideoInfo 3 }

erlyVideoInfoClients	OBJECT-TYPE
    	SYNTAX		INTEGER (1..65535)
	MAX-ACCESS	read-only
	STATUS		current
	DESCRIPTION
	    "Текущее количество клиентов"
	::= { erlyVideoInfo 4 }

erlyVideoStatTable OBJECT-TYPE
    	SYNTAX	 SEQUENCE OF erlyVideoStatEntry
	MAX-ACCESS not-accessible
	STATUS	 current
	DESCRIPTION
	    "Статистика на каждого клиента"
	::= { erlyVideo 2 }

erlyVideoStatEntry OBJECT-TYPE
    	SYNTAX	ErlyVideoStatEntry
	MAX-ACCESS	not-accessible
	STATUS   current
	DESCRIPTION
	    "Стат. данные на одного клиента"
	INDEX       { erlyVideoStatSesionId }
	::= { erlyVideoStatTable 1 }

ErlyVideoStatEntry ::= SEQUENCE {
	erlyVideoStatSesionId		OCTET STRING (SIZE(32)),
	erlyVideoStatUserId		DisplayString (SIZE(1..64)),
	erlyVideoStatRemoteIP		IpAddress,
	erlyVideoStatRemoteTCPPort	INTEGER (0..65535),
	erlyVideoStatBytesSend		Counter64,
	erlyVideoStatBytesRecv		Counter64
	}

erlyVideoStatSesionId	OBJECT-TYPE
    	SYNTAX		OCTET STRING (SIZE(32))
	MAX-ACCESS	read-only
	STATUS		current
	DESCRIPTION	" session_id "
	::= { erlyVideoStatEntry 1 }

erlyVideoStatUserId	OBJECT-TYPE
    	SYNTAX		DisplayString (SIZE(1..64))
	MAX-ACCESS	read-only
	STATUS		current
	DESCRIPTION	" user_id "
	::= { erlyVideoStatEntry 2 }

erlyVideoStatRemoteIP	OBJECT-TYPE
    	SYNTAX		IpAddress
	MAX-ACCESS	read-only
	STATUS		current
	DESCRIPTION	" ip клиента "
	::= { erlyVideoStatEntry 3 }

erlyVideoStatRemoteTCPPort	OBJECT-TYPE
    	SYNTAX		INTEGER (0..65535)
	MAX-ACCESS	read-only
	STATUS		current
	DESCRIPTION	" tcp port клиента "
	::= { erlyVideoStatEntry 4 }

erlyVideoStatBytesSend	OBJECT-TYPE
    	SYNTAX		Counter64
	MAX-ACCESS	read-only
	STATUS		current
	DESCRIPTION	" посланно байт клиенту (без учета? tcp/rtp/прочих заголовков) "
	::= { erlyVideoStatEntry 5 }
	
erlyVideoStatBytesRecv	OBJECT-TYPE
    	SYNTAX		Counter64
	MAX-ACCESS	read-only
	STATUS		current
	DESCRIPTION	" полученно байт от клиента (без учета? tcp/rtp/прочих заголовков) "
	::= { erlyVideoStatEntry 6 }
	
erlyVideoStreamTable OBJECT-TYPE
    	SYNTAX	 SEQUENCE OF erlyVideoStreamEntry
	MAX-ACCESS not-accessible
	STATUS	 current
	DESCRIPTION
	    "Имеющиеся стримы"
	::= { erlyVideo 3 }

erlyVideoStreamEntry OBJECT-TYPE
    	SYNTAX	ErlyVideoStreamEntry
	MAX-ACCESS	not-accessible
	STATUS   current
	DESCRIPTION
	    "Информация об одном стриме"
	INDEX       { erlyVideoStreamVhost, erlyVideoStreamName }
	::= { erlyVideoStreamTable 1 }

ErlyVideoStreamEntry ::= SEQUENCE {
	erlyVideoStreamVhost		DisplayString (SIZE(1..255)),
	erlyVideoStreamName		DisplayString (SIZE(1..255)),
	erlyVideoStreamDest		DisplayString (SIZE(1..4096))
	}

erlyVideoStreamVhost	OBJECT-TYPE
    	SYNTAX		DisplayString (SIZE(1..255))
	MAX-ACCESS	read-only
	STATUS		current
	DESCRIPTION
	    "vhost данного стрима"
	::= { erlyVideoStreamEntry 1 }

erlyVideoStreamName	OBJECT-TYPE
    	SYNTAX		DisplayString (SIZE(1..255))
	MAX-ACCESS	read-only
	STATUS		current
	DESCRIPTION
	    "имя данного стрима"
	::= { erlyVideoStreamEntry 2 }

erlyVideoStreamDest	OBJECT-TYPE
    	SYNTAX		DisplayString (SIZE(1..255))
	MAX-ACCESS	read-only
	STATUS		current
	DESCRIPTION
	    "что отдается в качестве данного стрима"
	::= { erlyVideoStreamEntry 3 }



END
